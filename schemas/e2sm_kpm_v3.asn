-- E2SM-KPM v3.0 ASN.1 Schema (O-RAN.WG3.E2SM-KPM-v03.00)
-- Simplified schema for asn1tools APER codec compilation.
-- Extended with NTN measurement fields for multi-orbit handover.
--
-- This is a minimal working subset sufficient for the xApp to
-- decode E2SM-KPM indication headers/messages from OSC RIC.
-- Full schema available from O-RAN Alliance specifications.

E2SM-KPM-IEs {
    iso(1) identified-organization(3) dod(6) internet(1)
    private(4) enterprise(1) oran(53148) e2(1)
    version1(1) e2sm(2) e2sm-kpm-ies(2)
}

DEFINITIONS AUTOMATIC TAGS ::=

BEGIN

IMPORTS
    ;

-- Indication Header
E2SM-KPM-IndicationHeader ::= CHOICE {
    indicationHeader-Format1    E2SM-KPM-IndicationHeader-Format1,
    ...
}

E2SM-KPM-IndicationHeader-Format1 ::= SEQUENCE {
    colletStartTime     OCTET STRING (SIZE(4)),
    fileFormatversion   PrintableString (SIZE(0..15))    OPTIONAL,
    senderName          PrintableString (SIZE(0..400))   OPTIONAL,
    senderType          PrintableString (SIZE(0..8))     OPTIONAL,
    vendorName          PrintableString (SIZE(0..32))    OPTIONAL,
    ...
}

-- Indication Message
E2SM-KPM-IndicationMessage ::= CHOICE {
    indicationMessage-Format1   E2SM-KPM-IndicationMessage-Format1,
    indicationMessage-Format2   E2SM-KPM-IndicationMessage-Format2,
    indicationMessage-Format3   E2SM-KPM-IndicationMessage-Format3,
    ...
}

E2SM-KPM-IndicationMessage-Format1 ::= SEQUENCE {
    measData        MeasurementData,
    measInfoList    MeasurementInfoList      OPTIONAL,
    granulPeriod    GranularityPeriod        OPTIONAL,
    ...
}

E2SM-KPM-IndicationMessage-Format2 ::= SEQUENCE {
    measData            MeasurementData,
    measCondUEidList    MeasurementCondUEidList,
    granulPeriod        GranularityPeriod        OPTIONAL,
    ...
}

E2SM-KPM-IndicationMessage-Format3 ::= SEQUENCE {
    ueMeasReportList    UEMeasurementReportList,
    ...
}

-- Supporting types
MeasurementData ::= SEQUENCE (SIZE(1..65535)) OF MeasurementDataItem

MeasurementDataItem ::= SEQUENCE {
    measRecord      MeasurementRecord,
    incompleteFlag  ENUMERATED {true, ...}  OPTIONAL,
    ...
}

MeasurementRecord ::= SEQUENCE (SIZE(1..2147483647)) OF MeasurementRecordItem

MeasurementRecordItem ::= CHOICE {
    integer     INTEGER (0..4294967295),
    real        REAL,
    noValue     NULL,
    ...
}

MeasurementInfoList ::= SEQUENCE (SIZE(1..65535)) OF MeasurementInfoItem

MeasurementInfoItem ::= SEQUENCE {
    measType    MeasurementType,
    labelInfoList   LabelInfoList   OPTIONAL,
    ...
}

MeasurementType ::= CHOICE {
    measName    PrintableString (SIZE(1..150)),
    measID      INTEGER (1..65536),
    ...
}

LabelInfoList ::= SEQUENCE (SIZE(1..2147483647)) OF LabelInfoItem

LabelInfoItem ::= SEQUENCE {
    measLabel   MeasurementLabel,
    ...
}

MeasurementLabel ::= SEQUENCE {
    noLabel                 ENUMERATED {true, ...}    OPTIONAL,
    plmnID                  OCTET STRING (SIZE(3))    OPTIONAL,
    sliceID                 OCTET STRING              OPTIONAL,
    fiveQI                  INTEGER (0..255)          OPTIONAL,
    qFI                     INTEGER (0..63)           OPTIONAL,
    qCI                     INTEGER (0..255)          OPTIONAL,
    qCImax                  INTEGER (0..255)          OPTIONAL,
    qCImin                  INTEGER (0..255)          OPTIONAL,
    aRPmax                  INTEGER (1..15)           OPTIONAL,
    aRPmin                  INTEGER (1..15)           OPTIONAL,
    ...
}

GranularityPeriod ::= INTEGER (1..4294967295)

MeasurementCondUEidList ::= SEQUENCE (SIZE(1..65535)) OF MeasurementCondUEidItem

MeasurementCondUEidItem ::= SEQUENCE {
    measType            MeasurementType,
    matchingCond        MatchingCondList,
    matchingUEidList    MatchingUEidList    OPTIONAL,
    ...
}

MatchingCondList ::= SEQUENCE (SIZE(1..32768)) OF MatchingCondItem

MatchingCondItem ::= CHOICE {
    measLabel       MeasurementLabel,
    testCondInfo    TestCondInfo,
    ...
}

TestCondInfo ::= SEQUENCE {
    testType    TestCond-Type,
    testExpr    TestCond-Expression      OPTIONAL,
    testValue   TestCond-Value           OPTIONAL,
    ...
}

TestCond-Type ::= CHOICE {
    gBR     ENUMERATED {true, ...},
    aMBR    ENUMERATED {true, ...},
    isStat  ENUMERATED {true, ...},
    isCatM  ENUMERATED {true, ...},
    rSRP    ENUMERATED {true, ...},
    rSRQ    ENUMERATED {true, ...},
    ...
}

TestCond-Expression ::= ENUMERATED {
    equal,
    greaterthan,
    lessthan,
    contains,
    present,
    ...
}

TestCond-Value ::= CHOICE {
    valueInt    INTEGER,
    valueEnum   INTEGER,
    valueBool   BOOLEAN,
    valueBitS   BIT STRING,
    valueOctS   OCTET STRING,
    valuePrtS   PrintableString,
    valueReal   REAL,
    ...
}

MatchingUEidList ::= SEQUENCE (SIZE(1..65535)) OF MatchingUEidItem

MatchingUEidItem ::= SEQUENCE {
    ueID    UEID,
    ...
}

UEMeasurementReportList ::= SEQUENCE (SIZE(1..65535)) OF UEMeasurementReportItem

UEMeasurementReportItem ::= SEQUENCE {
    ueID        UEID,
    measReport  E2SM-KPM-IndicationMessage-Format1,
    ...
}

UEID ::= CHOICE {
    gNB-UEID       UEID-GNB,
    gNB-DU-UEID    UEID-GNB-DU,
    gNB-CU-UP-UEID UEID-GNB-CU-UP,
    ng-eNB-UEID    UEID-NG-ENB,
    ng-eNB-DU-UEID UEID-NG-ENB-DU,
    en-gNB-UEID    UEID-EN-GNB,
    eNB-UEID       UEID-ENB,
    ...
}

UEID-GNB ::= SEQUENCE {
    amf-UE-NGAP-ID     INTEGER (0..1099511627775),
    guami               GUAMI                           OPTIONAL,
    gNB-CU-UE-F1AP-ID  INTEGER (0..4294967295)          OPTIONAL,
    ...
}

UEID-GNB-DU ::= SEQUENCE {
    gNB-CU-UE-F1AP-ID  INTEGER (0..4294967295),
    ...
}

UEID-GNB-CU-UP ::= SEQUENCE {
    gNB-CU-CP-UE-E1AP-ID   INTEGER (0..4294967295),
    ...
}

UEID-NG-ENB ::= SEQUENCE {
    amf-UE-NGAP-ID     INTEGER (0..1099511627775),
    ...
}

UEID-NG-ENB-DU ::= SEQUENCE {
    ng-eNB-CU-UE-W1AP-ID   INTEGER (0..4294967295),
    ...
}

UEID-EN-GNB ::= SEQUENCE {
    m-eNB-UE-X2AP-ID       INTEGER (0..4095),
    ...
}

UEID-ENB ::= SEQUENCE {
    mME-UE-S1AP-ID     INTEGER (0..4294967295),
    ...
}

GUAMI ::= SEQUENCE {
    pLMNIdentity    OCTET STRING (SIZE(3)),
    aMFRegionID     BIT STRING (SIZE(8)),
    aMFSetID        BIT STRING (SIZE(10)),
    aMFPointer      BIT STRING (SIZE(6)),
    ...
}

END
